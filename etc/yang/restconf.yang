module restconf {
	namespace "http://org.conf2/ns/modules";
	prefix "modules";
	import conf2-management;
	revision 0;

    container controllerRegistry {
        leaf addr {
            type string;
        }
        leaf endpointId {
            type string;
        }
        leaf callbackAddr {
            type string;
        }
        list registrations {
            key "id";
            leaf id {
                type string;
            }
        }
    }

	list modules {
		key "name";
		config "false";
		leaf name {
			type string;
		}
		container module {
			/* replace with YANG-1.0 meta */
			leaf nop {
				type string;
			}
		}
	}
}
