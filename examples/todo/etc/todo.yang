module todo {
    namespace "todo";
    prefix "http://conf2.org/todo";
    revision 0;

    /*
      Storing TODOs in RESTCONF
    */
    list todos {
        key "id";
        leaf id {
            type int32;
        }
        leaf status {
            type enumeration {
                enum done;
                enum todo;
            }
            default "todo";
        }
        leaf summary {
            type string;
        }
        leaf description {
            type string;
        }
        leaf-list keywords {
            type string;
        }
        leaf dueDate {
            type int64;
        }
    }

    /*
      for simplicity, we copy definitions from conf2-management.yang, but it could
      easily be imported.
    */
    container restconf {
        leaf port {
            type string;
        }
        leaf docRoot {
            type string;
        }
        leaf path {
            type string;
            default "/restconf/";
        }
        leaf-list registrations {
            type string;
            config "false";
        }
    }
}
