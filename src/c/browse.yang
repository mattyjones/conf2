module browse {
    prefix "browse";
    namespace "conf2.org/browse";
    revision 0000-00-00 {
        description "api to browse package";
    }

    grouping selection {
        leaf browserHnd {
            type int64;
        }
        leaf path {
            type string;
        }
    }

    grouping walking-params {
        container from {
             uses selection;
        }
        container to {
             uses selection;
        }
        leaf path {
            type string;
        }
    }

    rpc insert {
        input {
            uses walking-params;
        }
    }
    rpc upsert {
        input {
            uses walking-params;
        }
    }
    rpc update {
        input {
            uses walking-params;
        }
    }
}
