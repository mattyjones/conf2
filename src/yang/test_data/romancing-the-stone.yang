module rtstone {
    namespace "rtstone";
    prefix "rtstone";
    revision 0000-00-00 {
        description "";
    }

    grouping position {
        leaf x {
            type int32;
        }
        leaf y {
            type int32;
        }
        leaf z {
            type int32;
        }
    }

    grouping team {
        leaf color {
            type enumeration {
                enum red;
                enum blue;
                enum green;
                enum yellow;
            };
        }
        leaf-list members {
            type string;
        }
        leaf spawn-point {
            uses position;
        }
        leaf base-position {
            uses position;
        }
    }

    container game {
        list teams {
            max-elements 4;
            container team {
                uses team;
            }
        }
        leaf base-radius {
            type int32;
        }
        list leaderboard {
            container entry {
                /* should be leaf-ref i guess */
                leaf team {
                    type "string";
                }
                leaf time {
                    type int32;
                }
            }
        }
        leaf time-limit {
            type int32;
        }
        list initial-inventory {
            container item {
                leaf item {
                    type int32;
                }
                leaf amount {
                    type int32;
                }
            }
        }
        list wardrobe {
            leaf item {
                type int32;
            }
        }
    }

    rpc start-game {
        input {
            leaf seconds-from-now {
                type int32;
            }
        }
    }
    rpc end-game {
        input {
            leaf seconds-from-now {
                type int32;
            }
        }
    }
    rpc restart-game {
        input {
            leaf seconds-from-now {
                type int32;
            }
        }
    }
}
