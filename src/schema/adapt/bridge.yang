module bridge {
    prefix "bridge";
    namespace "conf2.org/bridge";
    revision 0000-00-00;

    grouping meta-mapping {
        list mapping {
            key "from";
            leaf from {
                type string;
            }
            leaf to {
                type string;
            }
            uses meta-mapping;
        }
    }

    list bridges {
        key "name"
        leaf name {
            type string;
        }
        uses meta-mapping;
    }
}
