module browse {

    grouping value {
        switch x {
            case s {
                leaf str {
                    type string;
                }
            }
                ...
        }
    }

    grouping walkController {
        leaf maxDepth {
            type int32;
        }
        list initialKey {
            uses value;
        }
    }

    grouping selection {
        leaf browserHnd {
            type int64;
        }
        leaf path {
            type string;
        }
    }

    rpc insert {
        input {
            container from {
                 uses selection;
            }
            container to {
                 uses selection;
            }
            container controller {
                uses walkController;
            }
        }
    }
}
